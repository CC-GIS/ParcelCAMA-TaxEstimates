FME workspace 2022_ParcelCAMA_TaxRateEstimates.fmw

Parameters:
- SourceDataset_GEODATABASE_FILE_5 = \\CCPASR07\ncgs$\GIS Data\Mapping\docs\Schema.gdb   # File Geodatabase
- SourceDataset_XLSXR_5 = \\ccpasr07\GIS Data\Mapping\docs\Base_District_Reference.xlsx   # Source Microsoft Excel File(s)
- SourceDataset_XLSXR_4 = \\ccpasr07\GIS Data\Mapping\docs\Base_District_Reference.xlsx   # Source Microsoft Excel File(s)
- SourceDataset_GEODATABASE_FILE_3 = \\CCPASR36\OCMP$\GIS\ParcelCAMA_VISION.gdb   # File Geodatabase
- SourceDataset_GEODATABASE_FILE = \\CCPASR36\OCMP$\GIS\ParcelCAMA_VISION.gdb   # File Geodatabase
- SourceDataset_MSSQL_SPATIAL = CCWEB PROD   # SQL Server Connection

Readers:
- XLSXR_2: XLSXR from $(SourceDataset_XLSXR_5)
- XLSXR_3: XLSXR from $(SourceDataset_XLSXR_4)
- GEODATABASE_SDE_2: GEODATABASE_SDE
- GEODATABASE_FILE_4: GEODATABASE_FILE from $(SourceDataset_GEODATABASE_FILE_5)
- GEODATABASE_FILE_1: GEODATABASE_FILE from $(SourceDataset_GEODATABASE_FILE)
- GEODATABASE_SDE_1: GEODATABASE_SDE
- GEODATABASE_FILE_2: GEODATABASE_FILE from $(SourceDataset_GEODATABASE_FILE_3)
- MSSQL_SPATIAL_1: MSSQL_SPATIAL from $(SourceDataset_MSSQL_SPATIAL)

Note: PRODUCTION
Note: FME 2022
Creator_3
    GEOMTYPE = Geometry Object
    NUM = 1
    CREATED -> FeatureReader [INITIATOR]
FeatureReader
    ATTRIBUTES = dbo.Millfile,"District,Ward,TaxYear,TMR,TMO,TPC,TD,TP,PCTD,PCTP,SMR,SMO,SPC,SD,SP,PCSD,PCSP,LMR,S1MR,S1TaxName,Tolerance,MailDate,DiscDate,FaceDate1,FaceDate2,PenDate,LastDate,TaxDate,Line1,Line2,Line3,Line4,Line5,Line6,Line7,PLine1,PLine2,TCPhone,PrintEscrow,PrintPermit,LateMailDate,LateDiscDate,LateFaceDate1,LateFaceDate2,LatePenDate,LateLastDate,LateTaxDate,LateLine1,LateLine2,LateLine3,LateLine4,LateLine5,LateLine6,LateLine7,LatePLine1,LatePLine2,LateTCPhone,LatePrintEscrow,LatePrintPermit,Payment1Date,Payment2Date,Payment3Date,Payment4Date,Payment1Penalty,LatePayment1Date,LatePayment2Date,LatePayment3Date,LatePayment4Date,LatePayment1Penalty,SchoolFormula,SchoolStebRatio,SchoolMarketRatio,School1Formula,School1StebRatio,School1MarketRatio,HSExclusion,FSExclusion,HSFSOverride,HSOverride,FSOverride,BillCounty,BillTwp,BillSchool,BillCountyPC,BillTwpPC,BillSchoolPC,supplementalBillLine1,supplementalBillLine2,supplementalBillLine3,supplementalBillLine4,supplementalBillLine5,supplementalBillLine6,supplementalBillLine7",dbo.SpecTax,"District,Ward,TaxKey,TaxYear,Mill,Disc,Pen,Desc1,ExFlag,SpecFlag,TCPosition"
    ATTR_ACCUM_MODE = Only Use Result
    COMBINE_GEOM = Use Result
    DATASET = GSS
    FEATURETYPES = dbo.Millfile dbo.SpecTax
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = GSS
    MSSQL_ADO_QUERY_FEATURE_TYPES_FOR_MERGE_FILTERS = Yes
    MSSQL_ADO_READ_CACHE_SIZE = 10
    OUTPUT_FEATURES_DISPLAY = Schema and Data Features
    dbo.Millfile -> TestFilter_3
    dbo.Millfile -> TestFilter_4
    dbo.Millfile -> TestFilter
    dbo.SpecTax -> TestFilter_2
LandBase/CCMAP_SDE_ParcelCAMA (reader GEODATABASE_FILE_1) [off]
    attributes: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
CCMAP_SDE_ParcelCAMA (reader GEODATABASE_FILE_2) [off]
    attributes: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
Note: CCMAP TEST
ParcelCAMA (reader GEODATABASE_SDE_1) [off]
    attributes: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
Note: CCWEB
Note: PRODUCTION
Note: FME 2022
PARCELCAMA (reader MSSQL_SPATIAL_1)
    attributes: OBJECTID integer, OWNER2 nvarchar(40), SUBDIVISIO nvarchar(40), DEED_VERFY nvarchar(1), REF_FLAG nvarchar(40), YEAR_BLT smallint, TOTAL_VAL integer, TOTAL_ROOM smallint, TAX_STAT nvarchar(5), Suffix nvarchar(13), STORY_HEIG nvarchar(2), SQFT nvarchar(20), SITUS_ZIP integer, SITUS2 nvarchar(100), SITUS nvarchar(100), SCHOOL_DIST nvarchar(50), SALEPRICE integer, SALEDATE datetime2, PRIMARY_EX smallint, PIN nvarchar(15), PID integer, P_TYPE nvarchar(2), OWNER nvarchar(100), Notes nvarchar(100), NBHD_ID smallint, MUNI_NAME nvarchar(25), MUNI_CODE smallint, LUC smallint, Link nvarchar(30), last_edited_user nvarchar(255),
      last_edited_date datetime2, LAND_VAL integer, LAND_DESC nvarchar(100), HALF_BATH_ smallint, FULL_BATH_ smallint, FINISHED_B smallint, Fcode smallint, DWELLING_T smallint, DEEDED_AC numeric(6,2), DB_PG nvarchar(11), DataSource smallint, CTRL_NO integer, created_user nvarchar(255), created_date datetime2, CITY nvarchar(30), CARE_OF nvarchar(85), CalcAcre numeric(38,8), C_G_FLAG smallint, BLDG_VAL integer, BEDROOM_CO smallint, BASEMENT_P nvarchar(15), BASEMENT_G smallint, AIR_CONDIT smallint, AccuracyLevel smallint, GDB_GEOMATTR_DATA varbinary_max
    -> AttributeCreator
Note: FeatureJoiner_3 : Left
Junction_5
    -> Junction_6
Note: PRODUCTION
Note: FME 2022
Note: Export excel file to shared folder for Tax Assessment QC review
Note: DISPLAY Parcel map services are updated daily
AttributeCreator_4
    ATTR_TABLE:
      SET_TO TOTALTAX = FME_CONDITIONAL:DEFAULT_VALUE'_FME_NO_OP_'BOOL_OP;OR;COMPOSITE_TEST;1;TEST @Value(TAX_STAT) = X'0'FME_NUM_CONDITIONS2___
      SET_TO COUNTYTAX = FME_CONDITIONAL:DEFAULT_VALUE'_FME_NO_OP_'BOOL_OP;OR;COMPOSITE_TEST;1;TEST @Value(TAX_STAT) = X'0'FME_NUM_CONDITIONS2___
      SET_TO MUNICIPALTAX = FME_CONDITIONAL:DEFAULT_VALUE'_FME_NO_OP_'BOOL_OP;OR;COMPOSITE_TEST;1;TEST @Value(TAX_STAT) = X'0'FME_NUM_CONDITIONS2___
      SET_TO SCHOOLTAX = FME_CONDITIONAL:DEFAULT_VALUE'_FME_NO_OP_'BOOL_OP;OR;COMPOSITE_TEST;1;TEST @Value(TAX_STAT) = X'0'FME_NUM_CONDITIONS2___
      SET_TO VISION_URL_LINK = https://gis.vgsi.com/CumberlandcountyPA/Parcel.aspx?pid=@Value(PID)
    -> AttributeRemover
AttributeRemover
    REMOVE_ATTRS = BillCounty,BillSchool,BillSchoolPC,BillTwp,BillTwpPC,CurrentYearYesNo,DiscDate,District,FSExclusion,FSOverride,FaceDate1,FaceDate2,HSExclusion,HSFSOverride,HSOverride,JOININGDISTRICT,LMR,LastDate,LateDiscDate,LateFaceDate1,LateFaceDate2,LateLastDate,LateLine1,LateLine2,LateLine3,LateLine4,LateLine5,LateLine6,LateLine7,LateMailDate,LatePLine1,LatePLine2,LatePayment1Date,LatePayment1Penalty,LatePayment2Date,LatePayment3Date,LatePayment4Date,LatePenDate,LatePrintEscrow,LatePrintPermit,LateTCPhone,LateTaxDate,Line1,Line2,Line3,Line4,Line6,Line7,MailDate,Mill.sum,OBJECTID,PCSD,PCSP,PCTD,PCTP,PLine1,PLine2,Payment1Date,Payment1Penalty,Payment2Date,Payment3Date,PenDate,PrintEscrow,PrintPermit,S1MR,S1TaxName,SD,SMO,SMR,SP,SPC,School1Formula,School1MarketRatio,School1StebRatio,SchoolFormula,SchoolMarketRatio,SchoolStebRatio,Shape_Area,Shape_Length,TCPhone,TD,TMO,TMR,TP,TPC,TaxDate,TaxYear,Tolerance,Ward,created_date,last_edited_date,no_features,supplementalBillLine1,supplementalBillLine2,supplementalBillLine3,supplementalBillLine4,supplementalBillLine5,supplementalBillLine7,BillCountyPC,Line5,Payment4Date,supplementalBillLine6,Mill_sum,VISION_URL_LINK,COUNTYTAG,AccuracyLevel,DataSource,created_user,last_edited_user,CARE_OF
    -> BulkAttributeRemover
BulkAttributeRemover
    ATTR_EXP = geodb_feature_dataset
    -> AttributeCreator_11
Note: PRODUCTION
Note: ParcelCAMA_VISION.gdb / \\CCPASR36\OCMP$\GIS\ParcelCAMA_VISION.gdb
Note: FME 2022
FeatureWriter_2 [off]
    DATASET = \\CCPASR36\OCMP$\GIS\ParcelCAMA_VISION.gdb
    DATASET_ATTR = _dataset
    FEATURE_TYPE_LIST_ATTR = _feature_types
    FORMAT = GEODATABASE_FILE
    GEODATABASE_FILE_ANNOTATION_UNITS = unknown_units
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_ENABLE_LOAD_ONLY_MODE = no
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = NO
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 10000
    GEODATABASE_FILE_TRANSACTION_TYPE = TRANSACTIONS
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written
Note: CCMAP TEST
FeatureWriter [off]
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = W:\Map_Services_file_geodatabase_data_store\Connection_Files\CCMAP  NCGSSR07_GISTEST @ SDE.sde
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 10000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written

Bookmark: County Mill Tax Calculation
TestFilter_3
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) = 00
      NUM_TEST @Evaluate(@DateTimeFormat(@DateTimeNow(),%m)) >= 2
      NUM_TEST @Evaluate(@Value(TaxYear)) = @Evaluate(@DateTimeFormat(@DateTimeNow(),%Y))
      TEST SMR ATTRIBUTE_HAS_A_VALUE """,current year,"BOOL_OP,AND,COMPOSITE_TEST,""""""1 AND 2"""""",TEST_CLAUSE,TEST @Value(District) = 00
      NUM_TEST @Evaluate(@Value(TaxYear)) = @Evaluate(@DateTimeFormat(@DateTimeAdd(@DateTimeNow(),-P1Y),%Y))",Last year
    current year -> NoFeaturesTester_2
    Last year -> FeatureMerger_2 [REQUESTOR]
NoFeaturesTester_2
    NOINPUT -> AttributeCreator_8
    -> AttributeManager_3
AttributeCreator_8
    ATTR_TABLE = SET_TO CurrentYearYesNo = NO
    -> FeatureMerger_2 [SUPPLIER]
FeatureMerger_2
    ATTR_ACCUM_MODE = Merge Supplier
    ATTR_CONFLICT_RES = Use Requestor
    IGNORE_NULLS = No
    JOIN_KEYS = 0 0 AUTO
    MERGE_TYPE = Attributes Only
    PROCESS_DUPS = NO
    REJECT_NULL_MISSING_KEYS = No
    SUPPLIERS_FIRST = No
    MERGED -> Tester_2
Tester_2
    BOOL_OP = OR
    TEST_CLAUSE = TEST @Value(CurrentYearYesNo) = NO
    TEST_MODE = TEST
    PASSED -> AttributeManager_3
Note: COUNTYTAX = TotalVal * (SMR+LMR)/1000)
AttributeManager_3
    ATTR_TABLE = SET_TO COUNTYMILL = @div((@add(@Value(SMR),@Value(LMR))),1000)
    -> FeatureJoiner [RIGHT]
AttributeCreator
    ATTR_TABLE:
      SET_TO COUNTYTAX
      SET_TO MUNICIPALTAX
      SET_TO SCHOOLTAX
      SET_TO TOTALTAX
      SET_TO COUNTYTAG = 00
    -> FeatureJoiner [LEFT]
FeatureJoiner
    ATTR_CONFLICT_RES = Prefer Left
    GEOMETRY_HANDLING = Prefer Left
    JOIN_KEYS = COUNTYTAG District AUTO
    JOIN_MODE = Left
    JOINED -> AttributeManager
AttributeManager
    ATTR_TABLE:
      SET_TO COUNTYTAX = @int(@mult(@Value(TOTAL_VAL),@Value(COUNTYMILL)))
      SET_TO JOININGDISTRICT = @Substring(@Value(PIN),0,2)
    USER_EXPOSED_ATTRIBUTES = Shape_Length,Shape_Area,SHAPE.STArea(),SHAPE.STLength(),Mill_sum,MUNIMILL,SCHOOLMILL
    -> FeatureJoiner_2 [LEFT]

Bookmark: Accounts for Base Districts in Millfile
TestFilter_4
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) != 00
      NUM_TEST @Evaluate(@DateTimeFormat(@DateTimeNow(),%m)) >= 2
      NUM_TEST @Evaluate(@Value(TaxYear)) = @Evaluate(@DateTimeFormat(@DateTimeNow(),%Y))
      TEST TMR ATTRIBUTE_HAS_A_VALUE """,current year,"BOOL_OP,AND,COMPOSITE_TEST,""""""1 AND 2"""""",TEST_CLAUSE,TEST @Value(District) != 00
      NUM_TEST @Evaluate(@Value(TaxYear)) = @Evaluate(@DateTimeFormat(@DateTimeAdd(@DateTimeNow(),-P1Y),%Y))",Last year
    current year -> NoFeaturesTester_3
    Last year -> FeatureMerger_3 [REQUESTOR]
NoFeaturesTester_3
    NOINPUT -> AttributeCreator_9
    -> Junction
AttributeCreator_9
    ATTR_TABLE = SET_TO CurrentYearYesNo = NO
    -> FeatureMerger_3 [SUPPLIER]
FeatureMerger_3
    ATTR_ACCUM_MODE = Merge Supplier
    ATTR_CONFLICT_RES = Use Requestor
    IGNORE_NULLS = No
    JOIN_KEYS = 0 0 AUTO
    MERGE_TYPE = Attributes Only
    PROCESS_DUPS = NO
    REJECT_NULL_MISSING_KEYS = No
    SUPPLIERS_FIRST = No
    MERGED -> Tester_4
Tester_4
    BOOL_OP = OR
    TEST_CLAUSE = TEST @Value(CurrentYearYesNo) = NO
    TEST_MODE = TEST
    PASSED -> FeatureJoiner_4 [LEFT]
Note: FeatureJoiner_4
Junction
    -> Junction_2
Note: NoFeaturesTester_3
Junction_2
    -> FeatureJoiner_4 [LEFT]
Base_Millfile (reader XLSXR_2)
    attributes: District number(3,0), Base_District number(3,0)
    -> FeatureJoiner_4 [RIGHT]
FeatureJoiner_4
    ATTR_CONFLICT_RES = Prefer Left
    GEOMETRY_HANDLING = Prefer Left
    JOIN_KEYS = District District AUTO
    JOIN_MODE = Full
    JOINED -> Sorter
Sorter
    SORT_PARM = TMR NUMERIC DESCENDING
    SORTED -> Aggregator
Aggregator
    ACCUM_ATTRS_NAME = Use Attributes From One Feature
    AGGREGATE_TYPE = Homogeneous Collection (If Possible)
    CONCAT_ATTRS = District
    GROUP_BY = Base_District
    MODE = Geometry - Assemble One Level
    SEP = ,
    AGGREGATE -> AttributeSplitter
Note: Data Format Concern: Base Districts act as a relational data structure, but where is the relationship table stored? With only 50 district records there is little need to truncate the data.
AttributeSplitter
    ATTR_NAME = District
    DELIMITER = ,
    DROP_EMPTY_PARTS = No
    LIST_NAME = BASIC_District
    TRIM_OPTION = Both
    -> ListExploder
ListExploder
    ATTR_ACCUM_MODE = Prefix List Attributes
    INCOMING_PREFIX = LIST_
    INDEX_ATTR = _element_index
    LIST_ATTR = BASIC_District{}
    ELEMENTS -> AttributeManager_5
AttributeManager_5
    ATTR_TABLE:
      REMOVE Base_District
      REMOVE District
      RENAME_SET_VALUE TMR > Mill
      REMOVE SMR
      REMOVE LMR
      RENAME_SET_VALUE LIST_BASIC_District > District
      REMOVE _element_index
    -> StatisticsCalculator

Bookmark: Accounts for Base Districts in SpecTax
TestFilter_2
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) != 00
      NUM_TEST @Evaluate(@DateTimeFormat(@DateTimeNow(),%m)) >= 2
      NUM_TEST @Evaluate(@Value(TaxYear)) = @Evaluate(@DateTimeFormat(@DateTimeNow(),%Y))
      TEST Mill ATTRIBUTE_HAS_A_VALUE """,current year,"BOOL_OP,AND,COMPOSITE_TEST,""""""1 AND 2"""""",TEST_CLAUSE,TEST @Value(District) != 00
      NUM_TEST @Evaluate(@Value(TaxYear)) = @Evaluate(@DateTimeFormat(@DateTimeAdd(@DateTimeNow(),-P1Y),%Y))",Last year
    current year -> NoFeaturesTester_4
    Last year -> FeatureMerger_4 [REQUESTOR]
NoFeaturesTester_4
    NOINPUT -> AttributeCreator_10
    -> Junction_3
AttributeCreator_10
    ATTR_TABLE = SET_TO CurrentYearYesNo = NO
    -> FeatureMerger_4 [SUPPLIER]
FeatureMerger_4
    ATTR_ACCUM_MODE = Merge Supplier
    ATTR_CONFLICT_RES = Use Requestor
    IGNORE_NULLS = No
    JOIN_KEYS = 0 0 AUTO
    MERGE_TYPE = Attributes Only
    PROCESS_DUPS = NO
    REJECT_NULL_MISSING_KEYS = No
    SUPPLIERS_FIRST = No
    MERGED -> Tester_6
Tester_6
    BOOL_OP = OR
    TEST_CLAUSE = TEST @Value(CurrentYearYesNo) = NO
    TEST_MODE = TEST
    FAILED -> FeatureJoiner_5 [LEFT]
Note: FeatureJoiner_5
Junction_3
    -> Junction_4
Note: NoFeaturesTester_4
Junction_4
    -> FeatureJoiner_5 [LEFT]
Base_SpecTax (reader XLSXR_3)
    attributes: District number(3,0), Base_District number(3,0)
    -> FeatureJoiner_5 [RIGHT]
FeatureJoiner_5
    ATTR_CONFLICT_RES = Prefer Left
    GEOMETRY_HANDLING = Prefer Left
    JOIN_KEYS = District District AUTO
    JOIN_MODE = Full
    JOINED -> Tester_7
Tester_7
    BOOL_OP = OR
    TEST_CLAUSE = TEST @Value(SpecFlag) != Y
    TEST_MODE = TEST
    PASSED -> AttributeKeeper_3
Note: Data Format Concern: Base Districts in SpecTax table are inconsistently applied. For example, Carlilse districts 2, 3, 4, 5, and 6 are represented with records in the data but Carlisle districts 49, 50, and 51 have Base Districts relating to district 2. This data formatting inconsistency is flagrant.
AttributeKeeper_3
    CREATE_BULK_MODE_FEATURES = NO
    KEEP_ATTRS = District,Mill,TaxYear,Base_District
    -> AttributeCreator_6
AttributeCreator_6
    ATTR_TABLE = SET_TO Dist_Holder = @Value(District)
    -> Aggregator_2
Aggregator_2
    ACCUM_ATTRS_NAME = Use Attributes From One Feature
    AGGREGATE_TYPE = Homogeneous Collection (If Possible)
    CONCAT_ATTRS = Dist_Holder
    GROUP_BY = Dist_Holder
    MODE = Geometry - Assemble One Level
    SEP = ,
    SUM = Mill
    AGGREGATE -> Aggregator_3
Aggregator_3
    ACCUM_ATTRS_NAME = Use Attributes From One Feature
    AGGREGATE_TYPE = Homogeneous Collection (If Possible)
    CONCAT_ATTRS = District
    GROUP_BY = Base_District
    MODE = Geometry - Assemble One Level
    SEP = ,
    AGGREGATE -> AttributeSplitter_2
AttributeSplitter_2
    ATTR_NAME = District
    DELIMITER = ,
    DROP_EMPTY_PARTS = No
    LIST_NAME = District_Base
    TRIM_OPTION = Both
    -> ListExploder_2
ListExploder_2
    ATTR_ACCUM_MODE = Merge List Attributes
    ATTR_CONFLICT_RES = Use List Attribute Values
    INDEX_ATTR = _element_index
    LIST_ATTR = District_Base{}
    ELEMENTS -> Tester_5
Tester_5
    BOOL_OP = OR
    TEST_CLAUSE = TEST @Value(Mill) > 0
    TEST_MODE = TEST
    PASSED -> AttributeManager_8
AttributeManager_8
    ATTR_TABLE:
      REMOVE Base_District
      REMOVE Dist_Holder
      RENAME_SET_VALUE District_Base > District
      REMOVE _element_index
    -> StatisticsCalculator

Bookmark: School Mill Tax Calculator
TestFilter
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) != 00
      NUM_TEST @Evaluate(@DateTimeFormat(@DateTimeNow(),%m)) >= 7
      NUM_TEST @Evaluate(@Value(TaxYear)) = @Evaluate(@DateTimeFormat(@DateTimeNow(),%Y))
      TEST SMR ATTRIBUTE_HAS_A_VALUE """,current year,"BOOL_OP,AND,COMPOSITE_TEST,""""""1 AND 2"""""",TEST_CLAUSE,TEST @Value(District) != 00
      NUM_TEST @Evaluate(@Value(TaxYear)) = @Evaluate(@DateTimeFormat(@DateTimeAdd(@DateTimeNow(),-P1Y),%Y))",Last year
    current year -> NoFeaturesTester
    Last year -> FeatureMerger [REQUESTOR]
NoFeaturesTester
    NOINPUT -> AttributeCreator_2
    -> AttributeManager_2
AttributeCreator_2
    ATTR_TABLE = SET_TO CurrentYearYesNo = NO
    -> FeatureMerger [SUPPLIER]
FeatureMerger
    ATTR_ACCUM_MODE = Merge Supplier
    ATTR_CONFLICT_RES = Use Requestor
    IGNORE_NULLS = No
    JOIN_KEYS = 0 0 AUTO
    MERGE_TYPE = Attributes Only
    PROCESS_DUPS = NO
    REJECT_NULL_MISSING_KEYS = No
    SUPPLIERS_FIRST = No
    MERGED -> Tester_3
Tester_3
    BOOL_OP = OR
    TEST_CLAUSE = TEST @Value(CurrentYearYesNo) = NO
    TEST_MODE = TEST
    PASSED -> AttributeManager_2
AttributeManager_2
    ATTR_TABLE = RENAME_SET_VALUE SMR > SCHOOLMILL
    -> ExpressionEvaluator_5
Note: Data Format Concern: Mill rates are stored in tables with leading zeros removed. Leading zeros must be added for calculations or publishing.
ExpressionEvaluator_5
    ACTION = Create New Attribute
    EXPRESSION = @round(@div(@Value(SCHOOLMILL),1000),8)
    VAL_ATTR = SCHOOLMILL
    -> FeatureJoiner_3 [RIGHT]
Note: ExpressionEvaluator_2 : Output
Junction_6
    -> FeatureJoiner_3 [LEFT]
FeatureJoiner_3
    ATTR_CONFLICT_RES = Prefer Left
    GEOMETRY_HANDLING = Prefer Left
    JOIN_KEYS = JOININGDISTRICT District AUTO
    JOIN_MODE = Left
    JOINED -> ExpressionEvaluator_3
ExpressionEvaluator_3
    ACTION = Overwrite Existing Attributes
    ATTRLIST = SCHOOLTAX
    EXPRESSION = @int(@Value(TOTAL_VAL)*(@Value(SCHOOLMILL)))
    -> ExpressionEvaluator_4
ExpressionEvaluator_4
    ACTION = Overwrite Existing Attributes
    ATTRLIST = TOTALTAX
    EXPRESSION = @Value(COUNTYTAX)+@Value(MUNICIPALTAX)+@Value(SCHOOLTAX)
    -> AttributeCreator_4

Bookmark: Creates Districts that do not exist in GSS SQL tables
Creator_2 [off]
    GEOMTYPE = Geometry Object
    NUM = 1
    CREATED -> AttributeCreator_5
AttributeCreator_5 [off]
    ATTR_TABLE:
      SET_TO District = 28
      SET_TO TaxYear = @DateTimeFormat(@DateTimeNow(),%Y)
      SET_TO TMR = 0
    -> AttributeKeeper
AttributeKeeper [off]
    CREATE_BULK_MODE_FEATURES = NO
    KEEP_ATTRS = District,TaxYear,TMR

Bookmark: Testing School Tax current year, Input to TestFilter
Creator [off]
    GEOMTYPE = Geometry Object
    NUM = 1
    CREATED -> AttributeCreator_3 [off]
AttributeCreator_3 [off]
    ATTR_TABLE:
      SET_TO TaxYear = @DateTimeFormat(@DateTimeNow(),%Y)
      SET_TO District = 99
      SET_TO SMR = 9999
      SET_TO TaxMonth = @DateTimeFormat(@DateTimeNow(),%m)

Bookmark: New Bookmark
Note: This workbench is started when ParcelCAMA join workbech has completed
Note: Headless user connection for other people opening this workspace?
ParcelCAMA (reader GEODATABASE_SDE_2) [off]
    attributes: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

Bookmark: Municipal Mill Tax Calculator
Note: SQL Millfile has inconsistent Base Districts records between 2023 and 2024
StatisticsCalculator
    CALCULATION_MODE = NUMERIC
    FEAT_STATS = Mill,NUMERIC_MODE,,,,SUM,,,,,,,,,
    GROUP_BY = District
    SUMMARY -> ExpressionEvaluator
ExpressionEvaluator
    ACTION = Create New Attribute
    EXPRESSION = @round(@div(@Value(Mill.sum),1000),8)
    VAL_ATTR = MUNIMILL
    -> FeatureJoiner_2 [RIGHT]
FeatureJoiner_2
    ATTR_CONFLICT_RES = Prefer Left
    GEOMETRY_HANDLING = Prefer Left
    JOIN_KEYS = JOININGDISTRICT District AUTO
    JOIN_MODE = Left
    JOINED -> ExpressionEvaluator_2
ExpressionEvaluator_2
    ACTION = Overwrite Existing Attributes
    ATTRLIST = MUNICIPALTAX
    EXPRESSION = @int(@mult(@Value(TOTAL_VAL),@Value(MUNIMILL)))
    -> Junction_5

Bookmark: Tax Estimates Writers
AttributeCreator_11
    ATTR_TABLE = SET_TO fme_feature_type = ParcelCAMA_TaxEstimates
    -> FeatureWriter_3 [Output]
Note: CCWEB
FeatureWriter_3
    DATASET_ATTR = _dataset
    FEATURE_TYPE_LIST_ATTR = _feature_types
    FORMAT = GEODATABASE_SDE
    GEODATABASE_SDE_ANNOTATION_UNITS = unknown_units
    GEODATABASE_SDE_COMMIT_TRANSACTIONS_AFTER_WRITE = no
    GEODATABASE_SDE_CONNECTION_FILE = W:\Map_Services_file_geodatabase_data_store\Connection_Files\CCWEB on NCGSSR07GISPROD SDE.sde
    GEODATABASE_SDE_COORDINATE_SYSTEM_GRANULARITY = FEATURE_TYPE
    GEODATABASE_SDE_CREDENTIALS_OVERRIDE = NO
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 10000
    GEODATABASE_SDE_TRANSACTION_TYPE = TRANSACTIONS
    GEODATABASE_SDE_VALIDATE_FEATURES = no
    GEODATABASE_SDE_VERSION_OVERRIDE = NO
    GEODATABASE_SDE_XY_SCALE = 0
    GEODATABASE_SDE_Z_ORIGIN = 0
    GEODATABASE_SDE_Z_SCALE = 1
    TOTAL_FEATURES_WRITTEN_ATTR = _total_features_written
