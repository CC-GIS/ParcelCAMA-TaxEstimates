FME workspace TEST_ParcelCAMA_TaxRateEstimates.fmw

Parameters:
- SourceDataset_GEODATABASE_FILE_5 = \\CCPASR07\ncgs$\GIS Data\Mapping\docs\Schema.gdb   # File Geodatabase
- SourceDataset_XLSXR_5 = \\ccpasr07\GIS Data\Mapping\docs\Base_District_Reference.xlsx   # Source Microsoft Excel File(s)
- SourceDataset_XLSXR_4 = \\ccpasr07\GIS Data\Mapping\docs\Base_District_Reference.xlsx   # Source Microsoft Excel File(s)
- SourceDataset_GEODATABASE_SDE = CCMAP TEST SDE2   # ArcSDE Geodatabase Connection
- SourceDataset_GEODATABASE_FILE = \\CCPASR36\OCMP$\GIS\ParcelCAMA_VISION.gdb   # File Geodatabase

Readers:
- XLSXR_2: XLSXR from $(SourceDataset_XLSXR_5)
- XLSXR_3: XLSXR from $(SourceDataset_XLSXR_4)
- GEODATABASE_SDE_2: GEODATABASE_SDE
- GEODATABASE_FILE_4: GEODATABASE_FILE from $(SourceDataset_GEODATABASE_FILE_5)
- GEODATABASE_SDE_4: GEODATABASE_SDE from $(SourceDataset_GEODATABASE_SDE)
- GEODATABASE_FILE_1: GEODATABASE_FILE from $(SourceDataset_GEODATABASE_FILE)

Creator_3
    GEOMTYPE = Geometry Object
    NUM = 1
    CREATED -> FeatureReader [INITIATOR]
FeatureReader
    ATTRIBUTES = dbo.Millfile,"District,Ward,TaxYear,TMR,TMO,TPC,TD,TP,PCTD,PCTP,SMR,SMO,SPC,SD,SP,PCSD,PCSP,LMR,S1MR,S1TaxName,Tolerance,MailDate,DiscDate,FaceDate1,FaceDate2,PenDate,LastDate,TaxDate,Line1,Line2,Line3,Line4,Line5,Line6,Line7,PLine1,PLine2,TCPhone,PrintEscrow,PrintPermit,LateMailDate,LateDiscDate,LateFaceDate1,LateFaceDate2,LatePenDate,LateLastDate,LateTaxDate,LateLine1,LateLine2,LateLine3,LateLine4,LateLine5,LateLine6,LateLine7,LatePLine1,LatePLine2,LateTCPhone,LatePrintEscrow,LatePrintPermit,Payment1Date,Payment2Date,Payment3Date,Payment4Date,Payment1Penalty,LatePayment1Date,LatePayment2Date,LatePayment3Date,LatePayment4Date,LatePayment1Penalty,SchoolFormula,SchoolStebRatio,SchoolMarketRatio,School1Formula,School1StebRatio,School1MarketRatio,HSExclusion,FSExclusion,HSFSOverride,HSOverride,FSOverride,BillCounty,BillTwp,BillSchool,BillCountyPC,BillTwpPC,BillSchoolPC,supplementalBillLine1,supplementalBillLine2,supplementalBillLine3,supplementalBillLine4,supplementalBillLine5,supplementalBillLine6,supplementalBillLine7",dbo.SpecTax,"District,Ward,TaxKey,TaxYear,Mill,Disc,Pen,Desc1,ExFlag,SpecFlag,TCPosition"
    ATTR_ACCUM_MODE = Only Use Result
    COMBINE_GEOM = Use Result
    DATASET = GSS
    FEATURETYPES = dbo.Millfile dbo.SpecTax
    FORMAT = MSSQL_ADO
    INITIATOR_FIRST_OUTPUT = default
    MSSQL_ADO_APPLICATION_INTENT = ReadWrite
    MSSQL_ADO_COMMAND_TIMEOUT = 30
    MSSQL_ADO_CREATE_FEATURE_TABLES_FROM_DATA = Yes
    MSSQL_ADO_NAMED_CONNECTION = GSS
    MSSQL_ADO_QUERY_FEATURE_TYPES_FOR_MERGE_FILTERS = Yes
    MSSQL_ADO_READ_CACHE_SIZE = 10
    ORDER_RESULTS = No
    OUTPUT_ADD_SCHEMA_ATTRIBUTES = NO
    OUTPUT_FEATURES_DISPLAY = Schema and Data Features
    dbo.Millfile -> TestFilter
    dbo.Millfile -> TestFilter_4
    dbo.Millfile -> TestFilter_3
    dbo.SpecTax -> TestFilter_2
LandBase/CCMAP_SDE_ParcelCAMA (reader GEODATABASE_FILE_1)
    attributes: OBJECTID integer, VISION_URL_LINK char(255), PID char(255), SITUS_ZIP char(255), SCHOOL_DIST char(255), TOTALTAX char(200), COUNTYTAX char(200), MUNICIPALTAX char(200), SCHOOLTAX char(200), PIN char(15), Suffix char(20), Notes char(100), Link char(30), GIS_PIN char(20), GIS_PIN_SU char(20), APPENDPIN char(35), OWNER char(40), CARE_OF char(40), SITUS char(35), SITUS2 char(40), P_TYPE char(2), SUBDIVISIO char(40), LAND_DESC char(40), DB_PG char(15), TAX_STAT char(5), C_G_FLAG char(1), DEED_VERFY char(1), YEAR_BLT char(4), MUNI_CODE char(5), MUNI_NAME char(25),
      CTRL_NO char(10), STORY_HEIG char(10), DWELLING_T char(100), PRIMARY_EX char(40), AIR_CONDIT char(40), BASEMENT_P char(40), REF_FLAG char(40), SALEDATE date, CalcAcre double, LUC double, NBHD_ID double, DEEDED_AC double, SQFT double, LAND_VAL double, BLDG_VAL double, TOTAL_VAL double, SALEPRICE double, FINISHED_B integer, BASEMENT_G integer, FULL_BATH_ integer, HALF_BATH_ integer, TOTAL_ROOM integer, BEDROOM_CO integer, Fcode smallint, District char(2), TaxYear char(4), SMR double, LMR double, COUNTYMILL char(200), COUNTYTAG char(200),
      JOININGDISTRICT char(200), created_date date, last_edited_date date, OBJECTID_1 integer, TMR double, Ward char(1), TMO double, TPC double, TD integer, TP integer, PCTD integer, PCTP integer, SMO double, SPC double, SD integer, SP integer, PCSD integer, PCSP integer, S1MR double, S1TaxName char(10), Tolerance double, MailDate date, DiscDate date, FaceDate1 date, FaceDate2 date, PenDate date, LastDate date, TaxDate date, Line1 char(75), Line2 char(75),
      Line3 char(75), Line4 char(75), Line5 char(75), Line6 char(75), Line7 char(75), PLine1 char(75), PLine2 char(75), TCPhone char(50), PrintEscrow char(1), PrintPermit integer, LateMailDate date, LateDiscDate date, LateFaceDate1 date, LateFaceDate2 date, LatePenDate date, LateLastDate date, LateTaxDate date, LateLine1 char(75), LateLine2 char(75), LateLine3 char(75), LateLine4 char(75), LateLine5 char(75), LateLine6 char(75), LateLine7 char(75), LatePLine1 char(75), LatePLine2 char(75), LateTCPhone char(50), LatePrintEscrow char(1), LatePrintPermit integer, Payment1Date date,
      Payment2Date date, Payment3Date date, Payment4Date date, Payment1Penalty char(1), LatePayment1Date date, LatePayment2Date date, LatePayment3Date date, LatePayment4Date date, LatePayment1Penalty char(1), SchoolFormula char(1), SchoolStebRatio double, SchoolMarketRatio double, School1Formula char(1), School1StebRatio double, School1MarketRatio double, HSExclusion double, FSExclusion double, HSFSOverride char(1), HSOverride double, FSOverride double, BillCounty char(1), BillTwp char(1), BillSchool char(1), BillCountyPC char(1), BillTwpPC char(1), BillSchoolPC char(1), supplementalBillLine1 char(255), supplementalBillLine2 char(255), supplementalBillLine3 char(255), supplementalBillLine4 char(255),
      supplementalBillLine5 char(255), supplementalBillLine6 char(255), supplementalBillLine7 char(255), CurrentYearYesNo char(200), no_features char(200), Mill_sum double, MUNIMILL double, SCHOOLMILL double, SHAPE_Length double, SHAPE_Area double
    -> AttributeCreator
Note: CCMAP TEST
ParcelCAMA (reader GEODATABASE_SDE_4) [off]
    attributes: OBJECTID integer, Fcode smallint, PIN char(15), Suffix char(20), Notes char(100), Link char(30), CalcAcre double, created_date date, last_edited_date date, OBJECTID_1 integer, GIS_PIN_SU char(20), OWNER char(40), CARE_OF char(40), SITUS char(35), SITUS2 char(40), P_TYPE char(2), LUC double, SUBDIVISIO char(40), NBHD_ID double, LAND_DESC char(40), DB_PG char(15), DEEDED_AC double, SQFT double, TAX_STAT char(5), C_G_FLAG char(1), LAND_VAL double, BLDG_VAL double, TOTAL_VAL double, DEED_VERFY char(1), SALEPRICE double,
      SALEDATE date, YEAR_BLT char(4), MUNI_CODE char(5), MUNI_NAME char(25), CTRL_NO char(10), STORY_HEIG char(10), DWELLING_T char(100), FINISHED_B integer, BASEMENT_G integer, FULL_BATH_ integer, HALF_BATH_ integer, TOTAL_ROOM integer, BEDROOM_CO integer, PRIMARY_EX char(40), AIR_CONDIT char(40), BASEMENT_P char(40), REF_FLAG char(40), VISION_URL_LINK char(255), PID char(255), SITUS_ZIP char(255), SCHOOL_DIST char(255), Shape_Length double, Shape_Area double
    -> AttributeCreator
Note: FeatureJoiner_3 : Left
Junction_5
    -> Junction_6
Note: Export excel file to shared folder for Tax Assessment QC review
Note: DISPLAY Parcel map services are updated daily
AttributeCreator_4
    ATTR_TABLE:
      SET_TO TOTALTAX = FME_CONDITIONAL:DEFAULT_VALUE'_FME_NO_OP_'BOOL_OP;OR;COMPOSITE_TEST;1;TEST @Value(TAX_STAT) = X'0'FME_NUM_CONDITIONS2___
      SET_TO COUNTYTAX = FME_CONDITIONAL:DEFAULT_VALUE'_FME_NO_OP_'BOOL_OP;OR;COMPOSITE_TEST;1;TEST @Value(TAX_STAT) = X'0'FME_NUM_CONDITIONS2___
      SET_TO MUNICIPALTAX = FME_CONDITIONAL:DEFAULT_VALUE'_FME_NO_OP_'BOOL_OP;OR;COMPOSITE_TEST;1;TEST @Value(TAX_STAT) = X'0'FME_NUM_CONDITIONS2___
      SET_TO SCHOOLTAX = FME_CONDITIONAL:DEFAULT_VALUE'_FME_NO_OP_'BOOL_OP;OR;COMPOSITE_TEST;1;TEST @Value(TAX_STAT) = X'0'FME_NUM_CONDITIONS2___
      SET_TO VISION_URL_LINK = https://gis.vgsi.com/CumberlandcountyPA/Parcel.aspx?pid=@Value(PID)
    -> AttributeRemover
AttributeRemover
    REMOVE_ATTRS = BillCounty,BillSchool,BillSchoolPC,BillTwp,BillTwpPC,CurrentYearYesNo,DiscDate,District,FSExclusion,FSOverride,FaceDate1,FaceDate2,HSExclusion,HSFSOverride,HSOverride,JOININGDISTRICT,LMR,LastDate,LateDiscDate,LateFaceDate1,LateFaceDate2,LateLastDate,LateLine1,LateLine2,LateLine3,LateLine4,LateLine5,LateLine6,LateLine7,LateMailDate,LatePLine1,LatePLine2,LatePayment1Date,LatePayment1Penalty,LatePayment2Date,LatePayment3Date,LatePayment4Date,LatePenDate,LatePrintEscrow,LatePrintPermit,LateTCPhone,LateTaxDate,Line1,Line2,Line3,Line4,Line6,Line7,MailDate,Mill.sum,OBJECTID,OBJECTID_1,PCSD,PCSP,PCTD,PCTP,PLine1,PLine2,Payment1Date,Payment1Penalty,Payment2Date,Payment3Date,PenDate,PrintEscrow,PrintPermit,S1MR,S1TaxName,SD,SHAPE_Area,SHAPE_Length,SMO,SMR,SP,SPC,School1Formula,School1MarketRatio,School1StebRatio,SchoolFormula,SchoolMarketRatio,SchoolStebRatio,Shape_Area,Shape_Length,TCPhone,TD,TMO,TMR,TP,TPC,TaxDate,TaxYear,Tolerance,Ward,created_date,last_edited_date,no_features,supplementalBillLine1,supplementalBillLine2,supplementalBillLine3,supplementalBillLine4,supplementalBillLine5,supplementalBillLine7,BillCountyPC,GIS_PIN,GIS_PIN_SU,Line5,Payment4Date,supplementalBillLine6,APPENDPIN,Mill_sum
    -> AttributeCreator_11

Bookmark: County Mill Tax Calculation
TestFilter_3
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) = 00
      NUM_TEST @Evaluate(@DateTimeFormat(@DateTimeNow(),%m)) >= 2
      NUM_TEST @Evaluate(@Value(TaxYear)) = @Evaluate(@DateTimeFormat(@DateTimeNow(),%Y))
      TEST SMR ATTRIBUTE_HAS_A_VALUE """,current year,"BOOL_OP,AND,COMPOSITE_TEST,""""""1 AND 2"""""",TEST_CLAUSE,TEST @Value(District) = 00
      NUM_TEST @Evaluate(@Value(TaxYear)) = @Evaluate(@DateTimeFormat(@DateTimeAdd(@DateTimeNow(),-P1Y),%Y))",Last year
    current year -> NoFeaturesTester_2
    Last year -> FeatureMerger_2 [REQUESTOR]
NoFeaturesTester_2
    NOINPUT -> AttributeCreator_8
    -> AttributeManager_3
AttributeCreator_8
    ATTR_TABLE = SET_TO CurrentYearYesNo = NO
    -> FeatureMerger_2 [SUPPLIER]
FeatureMerger_2
    ATTR_ACCUM_MODE = Merge Supplier
    ATTR_CONFLICT_RES_LOOKUP = REQUESTOR_IF_CONFLICT
    IGNORE_NULLS = No
    JOIN_KEYS = 0 0 AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> Tester_2
Tester_2
    BOOL_OP = OR
    TEST_CLAUSE = TEST @Value(CurrentYearYesNo) = NO
    TEST_MODE = TEST
    PASSED -> AttributeManager_3
Note: COUNTYTAX = TotalVal * (SMR+LMR)/1000)
AttributeManager_3
    ATTR_TABLE = SET_TO COUNTYMILL = @div((@add(@Value(SMR),@Value(LMR))),1000)
    -> FeatureJoiner [RIGHT]
AttributeCreator
    ATTR_TABLE:
      SET_TO COUNTYTAX
      SET_TO MUNICIPALTAX
      SET_TO SCHOOLTAX
      SET_TO TOTALTAX
      SET_TO COUNTYTAG = 00
    -> FeatureJoiner [LEFT]
FeatureJoiner
    ATTR_CONFLICT_RES_LOOKUP = USE_LEFT
    GEOMETRY_HANDLING_LOOKUP = USE_LEFT
    JOIN_KEYS = COUNTYTAG District AUTO
    JOIN_MODE = Left
    ATTR_CONFLICT_RES = Prefer Left
    GEOMETRY_HANDLING = Prefer Left
    JOINED -> AttributeManager
AttributeManager
    ATTR_TABLE:
      SET_TO COUNTYTAX = @int(@mult(@Value(TOTAL_VAL),@Value(COUNTYMILL)))
      SET_TO JOININGDISTRICT = @Substring(@Value(PIN),0,2)
    USER_EXPOSED_ATTRIBUTES = Shape_Length,Shape_Area
    -> FeatureJoiner_2 [LEFT]

Bookmark: Accounts for Base Districts in Millfile
TestFilter_4
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) != 00
      NUM_TEST @Evaluate(@DateTimeFormat(@DateTimeNow(),%m)) >= 2
      NUM_TEST @Evaluate(@Value(TaxYear)) = @Evaluate(@DateTimeFormat(@DateTimeNow(),%Y))
      TEST TMR ATTRIBUTE_HAS_A_VALUE """,current year,"BOOL_OP,AND,COMPOSITE_TEST,""""""1 AND 2"""""",TEST_CLAUSE,TEST @Value(District) != 00
      NUM_TEST @Evaluate(@Value(TaxYear)) = @Evaluate(@DateTimeFormat(@DateTimeAdd(@DateTimeNow(),-P1Y),%Y))",Last year
    current year -> NoFeaturesTester_3
    Last year -> FeatureMerger_3 [REQUESTOR]
NoFeaturesTester_3
    NOINPUT -> AttributeCreator_9
    -> Junction
AttributeCreator_9
    ATTR_TABLE = SET_TO CurrentYearYesNo = NO
    -> FeatureMerger_3 [SUPPLIER]
FeatureMerger_3
    ATTR_ACCUM_MODE = Merge Supplier
    ATTR_CONFLICT_RES_LOOKUP = REQUESTOR_IF_CONFLICT
    IGNORE_NULLS = No
    JOIN_KEYS = 0 0 AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> Tester_4
Tester_4
    BOOL_OP = OR
    TEST_CLAUSE = TEST @Value(CurrentYearYesNo) = NO
    TEST_MODE = TEST
    PASSED -> FeatureJoiner_4 [LEFT]
Note: FeatureJoiner_4
Junction
    -> Junction_2
Note: NoFeaturesTester_3
Junction_2
    -> FeatureJoiner_4 [LEFT]
Base_Millfile (reader XLSXR_2)
    attributes: District number(3,0), Base_District number(3,0)
    -> FeatureJoiner_4 [RIGHT]
FeatureJoiner_4
    ATTR_CONFLICT_RES_LOOKUP = USE_LEFT
    GEOMETRY_HANDLING_LOOKUP = USE_LEFT
    JOIN_KEYS = District District AUTO
    JOIN_MODE = Full
    ATTR_CONFLICT_RES = Prefer Left
    GEOMETRY_HANDLING = Prefer Left
    JOINED -> Sorter
Sorter
    SORT_PARM = TMR NUMERIC DESCENDING
    SORTED -> Aggregator
Aggregator
    ACCUM_ATTRS = One
    AGGREGATE_TYPE = Homogeneous Collection (If Possible)
    CONCAT_ATTRS = District
    GROUP_BY = Base_District
    MODE = Geometry - Assemble One Level
    SEP = ,
    ACCUM_ATTRS_NAME = Use Attributes From One Feature
    AGGREGATE -> AttributeSplitter
Note: Data Format Concern: Base Districts act as a relational data structure, but where is the relationship table stored? With only 50 district records there is little need to truncate the data.
AttributeSplitter
    ATTR_NAME = District
    DELIMITER = ,
    DROP_EMPTY_PARTS = No
    LIST_NAME = BASIC_District
    TRIM_COMMAND = trim
    TRIM_OPTION = Both
    -> ListExploder
ListExploder
    INCOMING_PREFIX = LIST_
    INDEX_ATTR = _element_index
    LIST_ATTR = BASIC_District{}
    ATTR_ACCUM_MODE = Prefix List Attributes
    ELEMENTS -> AttributeManager_5
AttributeManager_5
    ATTR_TABLE:
      REMOVE Base_District
      REMOVE District
      RENAME_SET_VALUE TMR > Mill
      REMOVE SMR
      REMOVE LMR
      RENAME_SET_VALUE LIST_BASIC_District > District
      REMOVE _element_index
    -> StatisticsCalculator

Bookmark: Accounts for Base Districts in SpecTax
TestFilter_2
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) != 00
      NUM_TEST @Evaluate(@DateTimeFormat(@DateTimeNow(),%m)) >= 2
      NUM_TEST @Evaluate(@Value(TaxYear)) = @Evaluate(@DateTimeFormat(@DateTimeNow(),%Y))
      TEST Mill ATTRIBUTE_HAS_A_VALUE """,current year,"BOOL_OP,AND,COMPOSITE_TEST,""""""1 AND 2"""""",TEST_CLAUSE,TEST @Value(District) != 00
      NUM_TEST @Evaluate(@Value(TaxYear)) = @Evaluate(@DateTimeFormat(@DateTimeAdd(@DateTimeNow(),-P1Y),%Y))",Last year
    current year -> NoFeaturesTester_4
    Last year -> FeatureMerger_4 [REQUESTOR]
NoFeaturesTester_4
    NOINPUT -> AttributeCreator_10
    -> Junction_3
AttributeCreator_10
    ATTR_TABLE = SET_TO CurrentYearYesNo = NO
    -> FeatureMerger_4 [SUPPLIER]
FeatureMerger_4
    ATTR_ACCUM_MODE = Merge Supplier
    ATTR_CONFLICT_RES_LOOKUP = REQUESTOR_IF_CONFLICT
    IGNORE_NULLS = No
    JOIN_KEYS = 0 0 AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> Tester_6
Tester_6
    BOOL_OP = OR
    TEST_CLAUSE = TEST @Value(CurrentYearYesNo) = NO
    TEST_MODE = TEST
    FAILED -> FeatureJoiner_5 [LEFT]
Note: FeatureJoiner_5
Junction_3
    -> Junction_4
Note: NoFeaturesTester_4
Junction_4
    -> FeatureJoiner_5 [LEFT]
Base_SpecTax (reader XLSXR_3)
    attributes: District number(3,0), Base_District number(3,0)
    -> FeatureJoiner_5 [RIGHT]
FeatureJoiner_5
    ATTR_CONFLICT_RES_LOOKUP = USE_LEFT
    GEOMETRY_HANDLING_LOOKUP = USE_LEFT
    JOIN_KEYS = District District AUTO
    JOIN_MODE = Full
    ATTR_CONFLICT_RES = Prefer Left
    GEOMETRY_HANDLING = Prefer Left
    JOINED -> Tester_7
Tester_7
    BOOL_OP = OR
    TEST_CLAUSE = TEST @Value(SpecFlag) != Y
    TEST_MODE = TEST
    PASSED -> AttributeKeeper_3
Note: Data Format Concern: Base Districts in SpecTax table are inconsistently applied. For example, Carlilse districts 2, 3, 4, 5, and 6 are represented with records in the data but Carlisle districts 49, 50, and 51 have Base Districts relating to district 2. This data formatting inconsistency is flagrant.
AttributeKeeper_3
    CREATE_BULK_MODE_FEATURES = NO
    KEEP_ATTRS = District,Mill,TaxYear,Base_District
    -> AttributeCreator_6
AttributeCreator_6
    ATTR_TABLE = SET_TO Dist_Holder = @Value(District)
    -> Aggregator_2
Aggregator_2
    ACCUM_ATTRS = One
    AGGREGATE_TYPE = Homogeneous Collection (If Possible)
    CONCAT_ATTRS = Dist_Holder
    GROUP_BY = Dist_Holder
    MODE = Geometry - Assemble One Level
    SEP = ,
    SUM = Mill
    ACCUM_ATTRS_NAME = Use Attributes From One Feature
    AGGREGATE -> Aggregator_3
Aggregator_3
    ACCUM_ATTRS = One
    AGGREGATE_TYPE = Homogeneous Collection (If Possible)
    CONCAT_ATTRS = District
    GROUP_BY = Base_District
    MODE = Geometry - Assemble One Level
    SEP = ,
    ACCUM_ATTRS_NAME = Use Attributes From One Feature
    AGGREGATE -> AttributeSplitter_2
AttributeSplitter_2
    ATTR_NAME = District
    DELIMITER = ,
    DROP_EMPTY_PARTS = No
    LIST_NAME = District_Base
    TRIM_COMMAND = trim
    TRIM_OPTION = Both
    -> ListExploder_2
ListExploder_2
    ATTR_CONFLICT_RES_LOOKUP = INCOMING_IF_CONFLICT
    INDEX_ATTR = _element_index
    LIST_ATTR = District_Base{}
    ATTR_ACCUM_MODE = Merge List Attributes
    ATTR_CONFLICT_RES = Use List Attribute Values
    ELEMENTS -> Tester_5
Tester_5
    BOOL_OP = OR
    TEST_CLAUSE = TEST @Value(Mill) > 0
    TEST_MODE = TEST
    PASSED -> AttributeManager_8
AttributeManager_8
    ATTR_TABLE:
      REMOVE Base_District
      REMOVE Dist_Holder
      RENAME_SET_VALUE District_Base > District
      REMOVE _element_index
    -> StatisticsCalculator

Bookmark: School Mill Tax Calculator
TestFilter
    DEFAULT_VALUE = <UNFILTERED>
    PASSED_TEST_GROUP_OUTPUT = FIRST
    TEST_LIST:
      "BOOL_OP,AND,COMPOSITE_TEST,""""""1 AND 2 AND 3 AND 4"""""",TEST_CLAUSE,TEST @Value(District) != 00
      NUM_TEST @Evaluate(@DateTimeFormat(@DateTimeNow(),%m)) >= 7
      NUM_TEST @Evaluate(@Value(TaxYear)) = @Evaluate(@DateTimeFormat(@DateTimeNow(),%Y))
      TEST SMR ATTRIBUTE_HAS_A_VALUE """,current year,"BOOL_OP,AND,COMPOSITE_TEST,""""""1 AND 2"""""",TEST_CLAUSE,TEST @Value(District) != 00
      NUM_TEST @Evaluate(@Value(TaxYear)) = @Evaluate(@DateTimeFormat(@DateTimeAdd(@DateTimeNow(),-P1Y),%Y))",Last year
    current year -> NoFeaturesTester
    Last year -> FeatureMerger [REQUESTOR]
NoFeaturesTester
    NOINPUT -> AttributeCreator_2
    -> AttributeManager_2
AttributeCreator_2
    ATTR_TABLE = SET_TO CurrentYearYesNo = NO
    -> FeatureMerger [SUPPLIER]
FeatureMerger
    ATTR_ACCUM_MODE = Merge Supplier
    ATTR_CONFLICT_RES_LOOKUP = REQUESTOR_IF_CONFLICT
    IGNORE_NULLS = No
    JOIN_KEYS = 0 0 AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> Tester_3
Tester_3
    BOOL_OP = OR
    TEST_CLAUSE = TEST @Value(CurrentYearYesNo) = NO
    TEST_MODE = TEST
    PASSED -> AttributeManager_2
AttributeManager_2
    ATTR_TABLE = RENAME_SET_VALUE SMR > SCHOOLMILL
    -> ExpressionEvaluator_5
Note: Data Format Concern: Mill rates are stored in tables with leading zeros removed. Leading zeros must be added for calculations or publishing.
ExpressionEvaluator_5
    ACTION = Create New Attribute
    EXPRESSION = @round(@div(@Value(SCHOOLMILL),1000),8)
    VAL_ATTR = SCHOOLMILL
    -> FeatureJoiner_3 [RIGHT]
Note: ExpressionEvaluator_2 : Output
Junction_6
    -> FeatureJoiner_3 [LEFT]
FeatureJoiner_3
    ATTR_CONFLICT_RES_LOOKUP = USE_LEFT
    GEOMETRY_HANDLING_LOOKUP = USE_LEFT
    JOIN_KEYS = JOININGDISTRICT District AUTO
    JOIN_MODE = Left
    ATTR_CONFLICT_RES = Prefer Left
    GEOMETRY_HANDLING = Prefer Left
    JOINED -> ExpressionEvaluator_3
ExpressionEvaluator_3
    ACTION = Overwrite Existing Attributes
    ATTRLIST = SCHOOLTAX
    EXPRESSION = @int(@Value(TOTAL_VAL)*(@Value(SCHOOLMILL)))
    -> ExpressionEvaluator_4
ExpressionEvaluator_4
    ACTION = Overwrite Existing Attributes
    ATTRLIST = TOTALTAX
    EXPRESSION = @Value(COUNTYTAX)+@Value(MUNICIPALTAX)+@Value(SCHOOLTAX)
    -> AttributeCreator_4

Bookmark: New Bookmark
Creator_4
    GEOMTYPE = Geometry Object
    NUM = 1
    CREATED -> FeatureReader_2 [INITIATOR]
FeatureReader_2
    ATTRIBUTES = LandBase/ParcelCAMA,"OBJECTID,Fcode,PIN,Suffix,Notes,Link,CalcAcre,created_date,last_edited_date,OBJECTID_1,GIS_PIN,GIS_PIN_SU,APPENDPIN,OWNER,CARE_OF,SITUS,SITUS2,P_TYPE,LUC,SUBDIVISIO,NBHD_ID,LAND_DESC,DB_PG,DEEDED_AC,SQFT,TAX_STAT,C_G_FLAG,LAND_VAL,BLDG_VAL,TOTAL_VAL,DEED_VERFY,SALEPRICE,SALEDATE,YEAR_BLT,MUNI_CODE,MUNI_NAME,CTRL_NO,STORY_HEIG,DWELLING_T,FINISHED_B,BASEMENT_G,FULL_BATH_,HALF_BATH_,TOTAL_ROOM,BEDROOM_CO,PRIMARY_EX,AIR_CONDIT,BASEMENT_P,REF_FLAG,SHAPE_Length,SHAPE_Area",LandBase/Test,"OBJECTID,Fcode,PIN,Suffix,Notes,Link,CalcAcre,DataSource,AccuracyLevel,created_user,created_date,last_edited_user,last_edited_date,PID,SHORT_PIN,OWNER,CARE_OF,CITY,SITUS,SITUS2,DEEDED_AC,SQFT,LAND_VAL,BLDG_VAL,TOTAL_VAL,DB_PG,YEAR_BLT,MAP_NUMBER,SITUS_ZIP,MUNI_CODE,MUNI_NAME,SCHOOL_DISTRICT,TAX_STAT,LAND_DESC,CTRL_NO,C_G_FLAG,P_TYPE,LUC,GIS_PIN,GIS_PIN_SUFFIX,NBHD_ID,SALEPRICE,SALEDATE,STORY_HEIGHT,DWELLING_TYPE,FINISHED_BASEMENT_SQFT,BASEMENT_GARAGE_SQFT,FULL_BATH_COUNT,HALF_BATH_COUNT,TOTAL_ROOM_COUNT,BEDROOM_COUNT,PRIMARY_EXTERIOR,AIR_CONDITIONING,BASEMENT_PERCENTAGE,SHAPE_Length,SHAPE_Area",LandBase/VISION_ParcelCAMA,"OBJECTID,PID,Fcode,PIN,Suffix,Notes,Link,CalcAcre,OWNER,CARE_OF,SITUS,SITUS2,SITUS_ZIP,P_TYPE,LUC,SUBDIVISIO,NBHD_ID,LAND_DESC,DB_PG,DEEDED_AC,SQFT,TAX_STAT,C_G_FLAG,LAND_VAL,BLDG_VAL,TOTAL_VAL,DEED_VERFY,SALEPRICE,SALEDATE,YEAR_BLT,MUNI_CODE,MUNI_NAME,SCHOOL_DIST,CTRL_NO,STORY_HEIG,DWELLING_T,FINISHED_B,BASEMENT_G,FULL_BATH_,HALF_BATH_,TOTAL_ROOM,BEDROOM_CO,PRIMARY_EX,AIR_CONDIT,BASEMENT_P,REF_FLAG,APPENDPIN,created_date,last_edited_date,OBJECTID_1,SHAPE_Length,SHAPE_Area"
    ATTR_ACCUM_MODE = Only Use Result
    CLIP_TO_ENVELOPE = NO
    COMBINE_GEOM = Use Result
    DATASET = \\ccpasr07\NCGS$\edit\Cumberland_Vision.gdb
    FEATURETYPES = LandBase/VISION_ParcelCAMA
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_DISABLE_FEATURE_DATASET_ATTRIBUTE = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_REMOVE_FEATURE_DATASET = NO
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TRANSLATE_SPATIAL_DATA_ONLY = no
    GEODATABASE_FILE_USE_SEARCH_ENVELOPE = NO
    GEOMETRY_TYPES = LandBase/ParcelCAMA,"""SHAPE,fme_area""",LandBase/Test,"""SHAPE,fme_area""",LandBase/VISION_ParcelCAMA,"""SHAPE,fme_area"""
    INITIATOR_FIRST_OUTPUT = default
    INTERACT = NONE
    ORDER_RESULTS = No
    OUTPUT_ADD_SCHEMA_ATTRIBUTES = NO
    OUTPUT_FEATURES_DISPLAY = Schema and Data Features
Note: This workbench is started when ParcelCAMA join workbech has completed
Note: Headless user connection for other people opening this workspace?
ParcelCAMA (reader GEODATABASE_SDE_2)
    attributes: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

Bookmark: Creates Districts that do not exist in GSS SQL tables
Creator_2 [off]
    GEOMTYPE = Geometry Object
    NUM = 1
    CREATED -> AttributeCreator_5
AttributeCreator_5 [off]
    ATTR_TABLE:
      SET_TO District = 28
      SET_TO TaxYear = @DateTimeFormat(@DateTimeNow(),%Y)
      SET_TO TMR = 0
    -> AttributeKeeper
AttributeKeeper [off]
    CREATE_BULK_MODE_FEATURES = NO
    KEEP_ATTRS = District,TaxYear,TMR

Bookmark: Testing School Tax current year, Input to TestFilter
Creator [off]
    GEOMTYPE = Geometry Object
    NUM = 1
    CREATED -> AttributeCreator_3 [off]
AttributeCreator_3 [off]
    ATTR_TABLE:
      SET_TO TaxYear = @DateTimeFormat(@DateTimeNow(),%Y)
      SET_TO District = 99
      SET_TO SMR = 9999
      SET_TO TaxMonth = @DateTimeFormat(@DateTimeNow(),%m)

Bookmark: Municipal Mill Tax Calculator
Note: SQL Millfile has inconsistent Base Districts records between 2023 and 2024
StatisticsCalculator
    ATTR_ACCUM_MODE = None
    CALCULATION_MODE = NUMERIC
    FEAT_STATS = Mill,NUMERIC_MODE,,,,SUM,,,,,,,,,
    GROUP_BY = District
    SUMMARY -> ExpressionEvaluator
ExpressionEvaluator
    ACTION = Create New Attribute
    EXPRESSION = @round(@div(@Value(Mill.sum),1000),8)
    VAL_ATTR = MUNIMILL
    -> FeatureJoiner_2 [RIGHT]
FeatureJoiner_2
    ATTR_CONFLICT_RES_LOOKUP = USE_LEFT
    GEOMETRY_HANDLING_LOOKUP = USE_LEFT
    JOIN_KEYS = JOININGDISTRICT District AUTO
    JOIN_MODE = Left
    ATTR_CONFLICT_RES = Prefer Left
    GEOMETRY_HANDLING = Prefer Left
    JOINED -> ExpressionEvaluator_2
ExpressionEvaluator_2
    ACTION = Overwrite Existing Attributes
    ATTRLIST = MUNICIPALTAX
    EXPRESSION = @int(@mult(@Value(TOTAL_VAL),@Value(MUNIMILL)))
    -> Junction_5

Bookmark: Tax Estimates Writers
AttributeCreator_11
    ATTR_TABLE = SET_TO fme_feature_type = ParcelCAMA_TaxEstimates
    -> FeatureWriter [Output]
    -> FeatureWriter_2 [FeatureClass1]
Note: ParcelCAMA_VISION.gdb / \\CCPASR36\OCMP$\GIS\ParcelCAMA_VISION.gdb
FeatureWriter_2
    DATASET = \\CCPASR36\OCMP$\GIS\ParcelCAMA_VISION.gdb
    DATASET_ATTR = _dataset
    FEATURE_TYPE_LIST_ATTR = _feature_types
    FORMAT = GEODATABASE_FILE
    GEODATABASE_FILE_ALWAYS_CREATE_FEATURE_TYPES = NO
    GEODATABASE_FILE_ANNOTATION_UNITS = unknown_units
    GEODATABASE_FILE_CASE_CONTROL_ATTR_NAMES = none
    GEODATABASE_FILE_CASE_CONTROL_FT_NAMES = none
    GEODATABASE_FILE_COMPRESS_AT_END = no
    GEODATABASE_FILE_COORDINATE_SYSTEM_GRANULARITY = FEATURE_TYPE
    GEODATABASE_FILE_DEFAULT_Z_VALUE = 0
    GEODATABASE_FILE_DESTINATION_DATASETTYPE_VALIDATION = Yes
    GEODATABASE_FILE_DUMP_FAILED_FEATURES = no
    GEODATABASE_FILE_ENABLE_FAST_DELETES = yes
    GEODATABASE_FILE_ENABLE_LOAD_ONLY_MODE = no
    GEODATABASE_FILE_FEATURE_DATASET_HANDLING = WRITE
    GEODATABASE_FILE_GRID_1 = 0
    GEODATABASE_FILE_HAS_MEASURES = no
    GEODATABASE_FILE_HAS_Z_VALUES = auto_detect
    GEODATABASE_FILE_IGNORE_FAILED_FEATURE_ENTRY = no
    GEODATABASE_FILE_MAX_NUMBER_FAILED_FEATURES = -1
    GEODATABASE_FILE_OVERWRITE_GEODB = NO
    GEODATABASE_FILE_PRESERVE_GLOBALID = no
    GEODATABASE_FILE_REQUESTED_GEODATABASE_VERSION = CURRENT
    GEODATABASE_FILE_SIMPLIFY_GEOM = No
    GEODATABASE_FILE_SIMPLIFY_NETWORK_FEATURES = no
    GEODATABASE_FILE_TRANSACTION = 0
    GEODATABASE_FILE_TRANSACTION_INTERVAL = 1000
    GEODATABASE_FILE_TRANSACTION_TYPE = TRANSACTIONS
    GEODATABASE_FILE_VALIDATE_FEATURES = no
    GEODATABASE_FILE_XY_SCALE = 0
    GEODATABASE_FILE_X_ORIGIN = 0
    GEODATABASE_FILE_Y_ORIGIN = 0
    GEODATABASE_FILE_Z_ORIGIN = 0
    GEODATABASE_FILE_Z_SCALE = 0
    TOTAL_FEATURES_WRITTEN_ATTR = _total_features_written
Note: CCMAP TEST
FeatureWriter
    DATASET = CCMAP TEST SDE2
    DATASET_ATTR = _dataset
    FEATURE_TYPE_LIST_ATTR = _feature_types
    FORMAT = GEODATABASE_SDE
    GEODATABASE_SDE_ALWAYS_CREATE_FEATURE_TYPES = NO
    GEODATABASE_SDE_ANNOTATION_UNITS = unknown_units
    GEODATABASE_SDE_CASE_CONTROL_ATTR_NAMES = none
    GEODATABASE_SDE_CASE_CONTROL_FT_NAMES = none
    GEODATABASE_SDE_COMMIT_TRANSACTIONS_AFTER_WRITE = no
    GEODATABASE_SDE_COORDINATE_SYSTEM_GRANULARITY = FEATURE_TYPE
    GEODATABASE_SDE_DEFAULT_Z_VALUE = 0
    GEODATABASE_SDE_DELETE_CHILD_AFTER_RECONCILE_AND_POST = yes
    GEODATABASE_SDE_DUMP_FAILED_FEATURES = no
    GEODATABASE_SDE_ENABLE_FAST_DELETES = yes
    GEODATABASE_SDE_ENABLE_LOAD_ONLY_MODE = no
    GEODATABASE_SDE_FEATURE_DATASET_HANDLING = WRITE
    GEODATABASE_SDE_GRID_1 = 0
    GEODATABASE_SDE_HAS_MEASURES = no
    GEODATABASE_SDE_HAS_Z_VALUES = auto_detect
    GEODATABASE_SDE_IGNORE_FAILED_FEATURE_ENTRY = no
    GEODATABASE_SDE_MAX_NUMBER_FAILED_FEATURES = -1
    GEODATABASE_SDE_MEASURES_ORIGIN = 0
    GEODATABASE_SDE_MEASURES_SCALE = 100
    GEODATABASE_SDE_NAMED_CONNECTION = CCMAP TEST SDE2
    GEODATABASE_SDE_ORIGIN_X = 0
    GEODATABASE_SDE_ORIGIN_Y = 0
    GEODATABASE_SDE_PERSISTENT_CONNECTION = no
    GEODATABASE_SDE_PRESERVE_GLOBALID = no
    GEODATABASE_SDE_RECONCILE_AND_POST = no
    GEODATABASE_SDE_SIMPLIFY_GEOM = no
    GEODATABASE_SDE_SIMPLIFY_NETWORK_FEATURES = no
    GEODATABASE_SDE_TRANSACTION = 0
    GEODATABASE_SDE_TRANSACTION_INTERVAL = 1000
    GEODATABASE_SDE_TRANSACTION_TYPE = TRANSACTIONS
    GEODATABASE_SDE_VALIDATE_FEATURES = no
    GEODATABASE_SDE_XY_SCALE = 0
    GEODATABASE_SDE_Z_ORIGIN = 0
    GEODATABASE_SDE_Z_SCALE = 1
    TOTAL_FEATURES_WRITTEN_ATTR = _total_features_written
